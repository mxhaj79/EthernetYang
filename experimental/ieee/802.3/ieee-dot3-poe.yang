module ieee-dot3-poe{
  namespace "urn:ieee:params:xml:ns:yang:ieee-dot3-poe";
  prefix poe;
  
  /**imports**/
  import ietf-interfaces { 
    prefix if;
  }
  
  import ethernet { 
    prefix eth;
  }
  
  
  
  /**Meta information**/
  organization
  "Huawei Technologies";
  
  description
  "This module contains YANG defintions for confirguring and 
  managing ports with Power Over Ethernet feature defined by
  IEEE 802.3. It provdes funcitonality roughly equivalent to
  that of the POWER-ETHERNET-MIB defined in RFC3621.";
  
  revision 2016-08-26{
    description
    "Initial revision.";
  }

  /*Identities&typedef*/
  typedef percentage {
    description "Percentage value in integer format.";
    type uint8 {
      range "0..100";
    }
  }
      
  typedef detection-state {
    description
     "detection state of a port";
    reference
     "IEEE Std 802.3, 30.9.1.1.5";
       
    type enumeration {
      enum disabled {
        value 1;
        description "PSE disabled";
      }
      enum searching {
        value 2;
        description "PSE is searching";
      }
      enum deliveringPower {
        value 3;
        description "PSE is delivering power";
      }
      enum fault {
        value 4;
        description "PSE fault detected";
      }
      enum test {
        value 5;
        description "PSE test mode";
      }
      enum otherFault {
        value 6;
        description "PSE implementation specific fault detected";
      }
    }
  }
  
  typedef power-class {
    description
      "power class";
    reference
      "IEEE Std 802.3, 30.9.1.1.6 aPSEPowerClassification";
       
    type enumeration {
      enum class0 {
        value 1;
        description "class 0";
      }
      enum class1 {
        value 2;
        description "class 1";
      }
      enum class2 {
        value 3;
        description "class 2";
      }
      enum class3 {
        value 4;
        description "class 3";
      }
      enum class4 {
        value 5;
        description "class 4";
      }
      enum class5 {
        value 6;
        description "class 5";
      }
      enum class6 {
        value 7;
        description "class 6";
      }
      enum class7 {
        value 8;
        description "class 7";
      }
      enum class8 {
        value 9;
        description "class 8";
      }
    }
  }

  identity poe-port-event {
    description "Poe port event notification base type.";
  }
  
  identity power-status-event {
    description "Poe port power status change notification.";
    base poe-port-event ;
  }
  
  identity pd-connection-status-event {
    description "Poe port peer,the power device status change notification.";
    base poe-port-event ;
  }
  
  identity power-absence-event {
    description "Poe port power absence notification.";
    base poe-port-event ;
  }
  
  identity poe-power-module-event {
    description "Poe power module event notification base type.";
  }
  
  
  identity power-usage-alarm {
    base poe-power-module-event ;
    description
    "Base identity for power usage event";
  }
  
  
  identity pd-connection-status {
    description
      "Base identity for the PD connnection status";
  }
  
  identity pd-connected {
    base pd-connection-status;
    description
      "pd is connected";
  }
  
  identity pd-disconnected {
    base pd-connection-status;
    description
      "pd is disconnected";
  }
  
  identity pd-class-invalid {
    base pd-connection-status;
    description "pd class is invalid";
  }
  
  identity pd-class-over-current {
    base pd-connection-status;
    description "pd class is over current";
  }
  
 
  /*
   * Configuration
   */
  /*poe port*/
  augment "/if:interfaces/if:interface/eth:ethernet" {
    description
    "Augements ethernet interface configuration model with 
     nodes specific to DTE Power via MDI devices and ports";
    
    container poe-pse-port{
      presence
        "capable and Enables DTE Power via MDI on the interface";
      description
        "DTE Power via MDI port configuration";
      reference
        "802.3, 30.9.1";
        
      container poe-intf-config {
        description
         "Per-interface PSE port configuration nodes";
    
        leaf pse-enable {
          type boolean;
          default false;
          description
            "whether to enable the PSE function on the interface.";
          reference
            "802.3 30.9.1.1.2 aPSEAdminState";
        }
       
        leaf powering-pairs {
          description
           "Describes or controls the pairs in use. If the value of
            pethPsePortPowerPairsControl is true, this object is 
            writeable";
          
          reference
            "IEEE Std 802.3, 30.9.1.1.4 aPSEPowerPairs";
    
          type enumeration {
            enum signal {
              value 1;
              description
               "the signal pair is in use";
            }
            enum spare {
              value 2;
              description
               "the spare pair is in use";
            }
            enum both {
              value 3;
              description
               "4-pair powering which is for .bt devices";
            }
          }
        }
       
        leaf power-priority {
          type uint32;
          description
             "This object controls the priority of the port from the point
            of view of a power management algorithm.";
        }
       
        leaf type {
          type string;
          description
            "A manager will set the value of this variable to indicate
            the type of powered device that is connected to the port.
            The default value supplied by the agent if no value has
            ever been set should be a zero-length octet string";
        }
        
        leaf event-notification-enable {
          description "Poe port event notification switch.";
          type boolean ;
          default false ;
        }
      }
    }
  }

  /*
  * Operational
  */
  /*poe port*/
  augment "/if:interfaces-state/if:interface/eth:Ethernet" {
    description
      "Augments ethernet interface operational state model with nodes
       specific to DTE Power via MDI devices and ports";
    
    container poe-pse-port {
      description
        "Interface operational state for PoE port";
      presence
        "capable and Enables DTE Power via MDI on the interface";
            
      leaf pairs-control-ability {
        type boolean;
        default true;
        description
          "Describes the capability of controlling the power pairs
           functionality to switch pins for sourcing power.";
        reference
          "IEEE Std 802.3, 30.9.1.1.3 aPSEPowerPairsControlAbility";
      }
      
      leaf detection-status {
        type detection-state;
        description 
          "Describes the operational status of the port 
           PD detection.";
        reference
          "IEEE Std 802.3, 30.9.1.1.5 aPSEPowerDetectionStatus";
      }
      
      leaf classifications {
        description "power class of the port";
        reference
          "IEEE Std 802.3, 30.9.1.1.6 aPSEPowerClassfication";

        when "../detection-status = 'deliveringPower'" {
          description
            "This node only apply when the detection status is 
             delivering power.";
        }

        type power-class;
      }
      
      container poe-statistics {
        description "statistics information of the pse port";
     
        leaf power-denied {
          type uint32;
          description 
            "This counter is incremented when the PSE state diagram
             enters the state POWER_DENIED";
          reference
            "IEEE Std 802.3, 30.9.1.1.8 aPSEPowerDeniedCounter";
        }
         
        leaf invalid-signature {
          type uint32;
          description
            "This counter is incremented when the PSE state diagram
                enters the state SIGNATURE_INVALID.";
          reference
            "IEEE Std 802.3, 30.9.1.1.7 aPSEInvalidSignatureCounter";
        }
         
        leaf MPSabsent {
          type uint32;
          description
             "This counter is incremented when the PSE state diagram
             transitions directly from the state POWER_ON to the
             state IDLE due to tmpdo_timer_done being asserted";
          reference
            "IEEE Std 802.3, 30.9.1.1.11 aPSEMPSAbsentCounter";
        }
         
        leaf overload {
          type uint32;
          description
             "This counter is incremented when the PSE state diagram
             enters the state ERROR_DELAY_OVER.";
          reference
            "IEEE Std 802.3, 30.9.1.1.9 aPSEOverLoadCounter";
        }
        
        leaf short {
          type uint32;
          description
             "This counter is incremented when the PSE state diagram
             enters the state ERROR_DELAY_SHORT.";
          reference
            "IEEE Std 802.3, 30.9.1.1.10 aPSEShortCounter";
        }
        leaf cumulative-energy {
          type uint32;
          description "";
          reference
           "IEEE Std 802.3, 30.9.1.1.14 aPSECumulativeEnergy";
        }      
  
      }
       
      leaf actual-power {
        type decimal64 {
          fraction-digits 4 ;
        }
        
        units 'watt';
        description "the actual power drawn by a PD over the port";
        reference "IEEE Std 802.3, 30.9.1.1.12 aPSEActualPower.";
      }
      leaf power-accuracy {
        type uint32;
        units 'milliwatt';
        description 
          "An integer value indicating the accuracy 
           associated with aPSEActualPower in +/- milliwatts.";
        reference
           "IEEE Std 802.3, 30.9.1.1.13 aPSEPowerAccuracy";
      }
    }
  }
  
  /*main source*/
  container main-power-sources-state {
    config false;
       
    description
      "operational state for main power source";
       
    list main-power-source-entry {
      key "slot-id";
      description "main power source entry";
          
      leaf slot-id {
        description "Poe power module installed slot.";
        type uint32;
      }
          
      container power-info {
        description 
          "power information of the main power source";
        
        leaf total-power {
          type decimal64 {
            fraction-digits 4;
          }
          units 'watt';
          description
            "The nominal power of the PSE expressed in Watts";
        }
        
        leaf reserved-power {
          type percentage ;
          description
            "The percent of power that the system reserved.";
        }
        
        leaf consuming-power {
          type decimal64 {
            fraction-digits 4;
          }
          units 'watt';
          description
            "Measured usage power";
        }
        
        leaf remained-power {
          type decimal64 {
            fraction-digits 4 ;
          }
          units 'watt';
          description
            "total power * (1-reserved power)-consuming Power";
        }
        
        leaf peak-power {
          type decimal64 {
            fraction-digits 4;
          }
          units 'watt';
          description
            "the peak power";
        }
        
        leaf usage-threshold {
          type percentage ;
          
          description
            "The usage threshold expressed in percents for
             comparing the measured power and initiating
             an alarm if the threshold is exceeded.";
        }
        
      }

          
      leaf operStatus {
        type enumeration {
          enum on {
            value 1;
            description "the main pse is on";
          }
          enum off {
            value 2;
            description "the main pse is off";
          }
          enum faulty {
            value 3;
            description "the main pse is faulty";
          }
        }
      
        default on;
        description
          "The operational status of the main PSE";
      }
    }
  }
  
  container poe-system-config {
    description "Configurations of the poe system.";
    
    /* Poe power module usage alarm configuration */
    container main-power-usage-threshold {
      description "Poe power module per slot usage alarm threshold setting.";
      
      list threhold {
        key "slot-id";
        
        leaf slot-id {
          description "Poe module installed slot.";
          type uint32;
        }
        
        leaf usage-threshold {
          description
          "The usage threshold expressed in percents for 
           comparing the measured power and initiating an alarm 
           if the threshold is exceeded.";
          
          type percentage ;
        }
      }
    }
  }
    
  
   /*
   * Notifications
   */
  notification poe-port-notification {
    description "Port event notification when the notification switch is on.";
    
      list event {
      key "if-name event-type";
      
      leaf if-name {
        description "Poe port interface name";
        type string ;
      }
      
      leaf event-type {
        description "event type for poe port.";
        type identityref {
          base poe-port-event ;
        }
      }
      
      container event-content {
        description "Event notification content.";
        
        leaf detection-status {
          when " ../../event-type = 'poe:power-status-event' " ;
          type detection-state;
          description "detection status";
        }
        
        leaf pd-connection-events {
          when " ../../event-type = 'poe:pd-connection-status-event' " ;          
          
          mandatory true;
          type identityref {
            base pd-connection-status;
          }
        }
      }
    }
  }
        
   notification poe-power-notification {
    description "power event notification when the notification switch is on.";
    
      list event {
      key "slot-id event-type";
      
      leaf slot-id {
        description "Slot id of the power source";
        type uint8 ;
      }
      
      leaf event-type {
        description "event type for main power source.";
        type identityref {
          base poe-power-module-event ;
        }
      }
      
      container event-content {
        description "Event notification content.";
        
        container power-usage {
          when " ../../event-type = 'poe:power-usage-alarm' " ;
          
          leaf consuming-power {
            mandatory true;
            type uint32;
            description "consuming power";
          }
          
          leaf usage-threshold {
            type uint32;
            description "usage threshold";
          } 
        }
      }
    }
  }     


}

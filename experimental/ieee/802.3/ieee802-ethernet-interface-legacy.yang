module ieee802-ethernet-interface-legacy {
  yang-version "1.1";

  namespace
    "urn:ieee:srd:802.3:yang:ieee802-ethernet-interface-legacy";

  prefix eth-old;

  import ietf-yang-types {
    prefix yang;
  }

  import ietf-interfaces {
    prefix if;
  }

  import iana-if-type {
    prefix ianaift;
  }

  import ieee802-ethernet-interface {
    prefix eth-if;
  }

  organization
    "Web URL: http://www.ieee802.org/3/

     Working Group Chair:
       David Law
       dlaw@hpe.com

     Working Group Vice-chair:
       Adam Healey
       adam.healey@broadcom.com

     Acting YANG Data Model Definitions Task Force Chair:
       Yan Zhuang
       zhuangyan.zhuang@huawei.com

     Editor:
       Robert Wilton
       rwilton@cisco.com";

  contact
    "Robert Wilton - rwilton@cisco.com";
  
  description
    "This module contains YANG definitions for configuring IEEE 802.3
     Ethernet interfaces that are deprecated, and are no longer
     widely used in the industry.  The definitions are maintained for
     backwards compatibility purposes, but the general expectation is
     that this module is not anticipated to be widely implemented.";
  reference "IEEE 802.3-2015, unless dated explicitly";
  
  revision 2017-01-20 {
    description
      "Initial revision of YANG 'legacy' module for IEEE 802.3
       Ethernet interfaces";
    reference 
      "IEEE P802.3.2 (IEEE 802.3cf) YANG Data Model Definitions Task
       Force";
  }

  feature dynamic-rate-control {
    status deprecated;
    description
      "This feature indicates that the device supports Ethernet
       interfaces lowering the average data rate of the MAC sublayer,
       with frame granularity, by using Rate Control to dynamically
       increase the inter-packet gap for some types of Ethernet
       interface.

       Only valid for Ethernet interfaces operating at speeds above
       1000 Mb/s.";
    reference "IEEE 802.3, 30.3.1.1.33, aRateControlAbility";
  }

  feature csma-cd {
    status deprecated;
    description
      "This feature indicates that the device supports Ethernet
       interfaces running at half duplex using CSMA/CD.";
    reference "IEEE 802.3, XXX";
  }

  typedef dynamic-rate-control-type {
    type enumeration {
      enum disabled {
        description 
          "Dynamic rate control is disabled";
      }
    
      enum "sonet-oc192" {
        value 2;
        description 
          "Dynamic rate control is enabled for a 10GB/s Ethernet
           interface to the SONET/SDH OC192/STM64 speed.";
      }
    }
    default disabled;
    status deprecated;
    description
      "Allowed values for dynamic-rate-control";
    reference
      "IEEE 802.3, 4.4.2 ipgStretchRatio and 30.3.1.1.34,
       aRateControlStatus";
  }

  augment "/if:interfaces/if:interface/eth-if:ethernet" {
    when "if:type = 'ianaift:ethernetCsmacd'" {
      description "Applies to all Ethernet interfaces";
    }
    description
      "Augment with any deprecated Ethernet interface configuration
       parameters";

    leaf dynamic-rate-control {
      if-feature "dynamic-rate-control";
      type dynamic-rate-control-type;
      status deprecated;
      description
        "Enables dynamic rate control and specifies what speed the
         dynamic rate control is operating at.  The speeds that may
         be configured are constrained by the MAC data rate, and
         hardware support.";
        reference "IEEE 802.3, 30.3.1.1.34, aRateControlStatus";
    }
  }

  augment "/if:interfaces-state/if:interface/eth-if:ethernet/" + 
          "eth-if:capabilities" {
    when "if:type = 'ianaift:ethernetCsmacd'" {
      description "Applies to all Ethernet interfaces";
    }
    description
      "Augment with any deprecated Ethernet interface configuration
       capabilities";

    leaf dynamic-rate-control-supported {
      if-feature "dynamic-rate-control";
      type boolean;
      default false;
      description 
        "Indicates whether the Ethernet interface supports lowering
         the average data rate of the MAC sublayer, with frame
         granularity, by using Rate Control to dynamically increase
         the inter-packet gap.

         Only valid for Ethernet interfaces operating at speeds above
         1000 Mb/s.";
      reference "IEEE 802.3, 30.3.1.1.33, aRateControlAbility";
    }
  }

  augment "/if:interfaces-state/if:interface/eth-if:ethernet" {
    when "if:type = 'ianaift:ethernetCsmacd'" {
      description "Applies to all Ethernet interfaces";
    }
    description
      "Augment with any deprecated Ethernet interface configuration
       parameters";
  }

  augment "/if:interfaces-state/if:interface/eth-if:ethernet/" + 
          "eth-if:frame-statistics" {
    when "if:type = 'ianaift:ethernetCsmacd'" {
      description "Applies to all Ethernet interfaces";
    }
    description 
      "Augment with any deprecated Ethernet interface configuration
       parameters";

    container "csma-cd" {
      if-feature "csma-cd";
      status deprecated; // TODO - Do we need to mark leaves as well?
      description
        "Holds counters that are specific to CDMA/CD half duplex
         operation of Ethernet interfaces.

         Discontinuities in the values of the counters in this
         container can occur at re-initialization of the management
         system, and at other times as indicated by the value of the
         'discontinuity-time' leaf defined in the ietf-interfaces
         YANG module (RFC 7223).";
      
      leaf in-errors-sqe-test {
        type yang:counter64;
        units errors;
        status deprecated;
        description 
          "A count of times that the SQE TEST ERROR is received on a
           particular interface. The SQE TEST ERROR is set in
           accordance with the rules for verification of the SQE
           detection mechanism in the PLS Carrier Sense Function as
           described in IEEE 802.3, 7.2.4.6.

           This counter does not increment on Ethernet interfaces
           operating at speeds greater than 10 Mb/s, or on Ethernet
           interfaces operating in full-duplex mode.

           Discontinuities in the value of this counter can occur at
           re-initialization of the management system, and at other
           times as indicated by the value of the
           'discontinuity-time' leaf defined in the ietf-interfaces
           YANG module (RFC 7223).";
        reference 
          "IEEE 802.3, 7.2.4.6, also 30.3.2.1.4, aSQETestErrors";
      }

      leaf out-pkts-collision-single {
        type yang:counter64;
        units frames;
        status deprecated;
        description 
          "A count of frames that are involved in a single collision,
           and are subsequently transmitted successfully. A frame
           that is counted by an instance of this object is also
           counted by the corresponding instance of either
           'out-unicast-ptks', 'out-broadcast-pkts', or
           'out-multicast-pkts', and is not counted by the
           corresponding instance of the
           'out-ptks-collision-multiple'.
           
           This counter does not increment when the Ethernet
           interface is operating in full-duplex mode.

           Discontinuities in the value of this counter can occur at
           re-initialization of the management system, and at other
           times as indicated by the value of the
           'discontinuity-time' leaf defined in the ietf-interfaces
           YANG module (RFC 7223).";
        reference
          "IEEE 802.3, 30.3.1.1.3, aSingleCollisionFrames";
      }

      leaf out-pkts-collision-multiple {
        type yang:counter64;
        units frames;
        status deprecated;
        description 
          "A count of frames that are involved in multiple
           collisions, and are subsequently transmitted
           successfully. A frame that is counted by an instance of
           this object is also counted by the corresponding instance
           of either 'out-unicast-ptks', 'out-broadcast-pkts', or
           'out-multicast-pkts', and is not counted by the
           corresponding instance of the 'out-ptks-collision-single'.

           This counter does not increment when the Ethernet
           interface is operating in full-duplex mode.

           Discontinuities in the value of this counter can occur at
           re-initialization of the management system, and at other
           times as indicated by the value of the
           'discontinuity-time' leaf defined in the ietf-interfaces
           YANG module (RFC 7223).";
        reference
          "IEEE 802.3, 30.3.1.1.4, aMultipleCollisionFrames";
      }

      leaf out-pkts-deferred {
        type yang:counter64;
        units frames;
        status deprecated;
        description 
          "A count of frames for which the first transmission attempt
           on a particular Ethernet interface is delayed because the
           medium is busy.

           A deferred frame that is not subject to any number of
           collisions is not counted by an instance of
           'out-pkts-collision-single' or
           'out-pkts-collision-multiple' objects.

           This counter does not increment when the Ethernet
           interface is operating in full-duplex mode.

           Discontinuities in the value of this counter can occur at
           re-initialization of the management system, and at other
           times as indicated by the value of the
           'discontinuity-time' leaf defined in the ietf-interfaces
           YANG module (RFC 7223).";
        reference
          "IEEE 802.3, 30.3.1.1.9, aFramesWithDeferredXmissions";
      }

      leaf out-pkts-collisions-excessive {
        type yang:counter64;
        units frames;
        status deprecated;
        description 
          "A count of frames for which transmission on a particular
           Ethernet interface fails due to excessive collisions.
           
           This counter does not increment when the Ethernet
           interface is operating in full-duplex mode.

           Discontinuities in the value of this counter can occur at
           re-initialization of the management system, and at other
           times as indicated by the value of the
           'discontinuity-time' leaf defined in the ietf-interfaces
           YANG module (RFC 7223).";
        reference
          "IEEE 802.3, 30.3.1.1.11, aFramesAbortedDueToXSColls";
      }

      leaf out-collisions-late {
        type yang:counter64;
        units collisions;
        status deprecated;
        description 
          "The number of times that a collision is detected on a
           particular Ethernet interface later than one slotTime into
           the transmission of a packet.

           A (late) collision included in a count represented by an
           instance of this object is also considered as a (generic)
           collision for purposes of other collision-related
           statistics.

           This counter does not increment when the Ethernet
           interface is operating in full-duplex mode.

           Discontinuities in the value of this counter can occur at
           re-initialization of the management system, and at other
           times as indicated by the value of the
           'discontinuity-time' leaf defined in the ietf-interfaces
           YANG module (RFC 7223).";
        reference
          "IEEE 802.3, 30.3.1.1.10, aLateCollisions";
      }

      leaf out-errors-carrier-sense {
        type yang:counter64;
        units errors;
        status deprecated;
        description 
          "The number of times that the carrier sense condition was
           lost or never asserted when attempting to transmit a frame
           on a particular Ethernet interface.

           The count represented by an instance of this object is
           incremented at most once per transmission attempt, even if
           the carrier sense condition fluctuates during a
           transmission attempt.

           This counter does not increment when the Ethernet
           interface is operating in full-duplex mode.

           Discontinuities in the value of this counter can occur at
           re-initialization of the management system, and at other
           times as indicated by the value of the
           'discontinuity-time' leaf defined in the ietf-interfaces
           YANG module (RFC 7223).";
        reference
          "IEEE 802.3, 30.3.1.1.13, aCarrierSenseErrors";
      }

      // TODO - Not sure whether this should live under the
      // statistics or not.
      list collision-histogram {
        key collision-count;
        status deprecated;
        description
          "A collection of collision histograms for a particular
           interface.";
        reference
          "IEEE 802.3, 30.3.1.1.30, aCollisionFrames";
        leaf collision-count {
          type yang:counter64;
          units collisions;
          status deprecated;
          description
            "The number of per-frame media collisions for which a
             particular collision histogram cell represents the
             frequency on a particular interface.";
        }
        leaf collision-count-pkts {
          type yang:counter64;
          units frames;
          status deprecated;
          description 
            "A count of individual MAC frames for which the
             transmission (successful or otherwise) on a particular
             interface occurs after the frame has experienced exactly
             the number of collisions in the associated dot3CollCount
             object.

             For example, a frame which is transmitted on an
             interface after experiencing exactly 4 collisions would
             be indicated by incrementing only collision-count-pkts
             object associated with the collision-count value of
             4. No other instance of collision-count-pkts would be
             incremented in this example.

             This counter does not increment when the interface is
             operating in full-duplex mode.

             Discontinuities in the value of this counter can occur
             at re-initialization of the management system, and at
             other times as indicated by the value of the
             'discontinuity-time' leaf defined in the ietf-interfaces
             YANG module (RFC 7223).";
        }
      }
    }
  }
}
